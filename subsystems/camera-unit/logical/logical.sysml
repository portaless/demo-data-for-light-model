package CameraUnitLogical {
    doc /* Architecture du sous-système camera-unit, ancrée sur
         MsatLogical::PayloadModule::CameraUnit — étage 3 du cycle
         récursif, même structure ROFLP+IVVQ que les étages 1 et 2. */
    ref part root : MsatLogical::PayloadModule::CameraUnit;
}
